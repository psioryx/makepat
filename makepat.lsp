;; MAKEPAT.LSP
;; Initial version 1998 J. Hoyt (psioryx)
;; Released under MIT License 2014

(defun c:fixangles()
  (setvar "cmdecho" 0)
  (Load_Master_Data)
  (setq ss2 (ssget nil))
  (if (> (sslength ss2) 0) (Alter_Angle_Data) (princ "No Lines found!\n"))
  (setq MASTER nil ss2 nil)
  (setvar "cmdecho" 1)
  (princ "\rAll done!            ")
  (princ)
)

(defun c:makepat()
  (setvar "cmdecho" 0)
  (setq fname (getstring "Pattern name: "))
  (setq ss2 (ssget nil))
  (if (> (sslength ss2) 0) (Create_Vectors) (princ "No Lines found!\n"))
  (setq MASTER nil ss2 nil)
  (setvar "cmdecho" 1)
  (princ "\rAll done!            ")
  (princ)
)

(defun Create_Vectors(/ ii oo cl sx sy ex ey ta ma mr ms me)
  (princ "\n\n\nLoading Data...\n")
  (Load_Master_Data)
  (setq fd (open (strcat fname ".pat") "w"))
  (write-line (strcat "*" fname ", " fname) fd)
  (setq cl 0 ms 0 ma 400.0 mr 0)
  (princ (strcat (itoa (sslength ss2)) " Objects Found...\n")  )
  (princ "Outputting Vectors...\n")
  (while (< cl (sslength ss2))
    (setq ii(entget (ssname ss2 cl)))
    (setq sx(nth 1 (assoc 10 ii)) sy(nth 2 (assoc 10 ii)) ex(nth 1 (assoc 11 ii)) ey(nth 2 (assoc 11 ii)) sp(list sx sy) ep(list ex ey))
    (setq la (atof (angtos (angle sp ep) 0 8)))
    (setq ms (fix (- (* la 2.22) 10))) (if (< ms 0) (setq ms (fix 0)))  
    (setq me (fix (+ (* la 2.22) 10))) (if (> me (length MASTER)) (setq me (fix (length MASTER))))
    (while (< ms me)
      (setq oo (nth 0 (nth ms MASTER)))
      (setq ta (abs (- (abs la) (abs oo))))
      (if (< ta ma) (setq ma ta mr ms))
      (setq ms (+ 1 ms))
    )
    (setq cl (+ 1 cl))
    (write-line (strcat (angtos (* pi (/ (nth 0 (nth mr MASTER)) 180)) 0 8)
                        ", "
                        (rtos sx 2 4)
                        ","
                        (rtos sy 2 4)
                        ", "
                        (rtos (nth 1 (nth mr MASTER)) 2 8)
                        ","
                        (rtos (nth 2 (nth mr MASTER)) 2 8)
                        ", "
                        (rtos (distance (list sx sy) (list ex ey)) 2 8)
                        ","
                        (rtos (- (distance (list sx sy) (list ex ey)) (nth 3 (nth mr MASTER))) 2 8)
                )
    fd)
    (entmod ii)
    (princ (strcat "\r" (itoa (- (sslength ss2) cl)) "     "))
    (setq ma 400 mr 0 ms 0)
  )
  (close fd)
)

(defun Alter_Angle_Data()
  (setq cl 0 ms 0 ma 400.0 mr 0)
  (princ (strcat (itoa (sslength ss2)) " Objects Found...\n")  )
  (princ "Altering Angles...\n")
  (while (< cl (sslength ss2))
    (setq ii(entget (ssname ss2 cl)))
    (setq sx(nth 1 (assoc 10 ii)) sy(nth 2 (assoc 10 ii)) ex(nth 1 (assoc 11 ii)) ey(nth 2 (assoc 11 ii)) sp(list sx sy) ep(list ex ey))
    (setq la (atof (angtos (angle sp ep) 0 8)))
    (setq ms (fix (- (* la 2.22) 10))) (if (< ms 0) (setq ms (fix 0)))  
    (setq me (fix (+ (* la 2.22) 10))) (if (> me (length MASTER)) (setq me (fix (length MASTER))))
    (while (< ms me)
      (setq oo (nth 0 (nth ms MASTER)))
      (setq ta (abs (- (abs la) (abs oo))))
      (if (< ta ma) (setq ma ta mr ms))
      (setq ms (+ 1 ms))
    )
    (setq cl (+ 1 cl))
    (setq ii (subst (cons 11 (polar (list sx sy) (setq blah (angtof (angtos (* pi (/ (nth 0 (nth mr MASTER)) 180)) 3 8) 3)) (distance (list sx sy) (list ex ey)) )
                    )
                    (assoc 11 ii)
                    ii
             )
    )
    (entmod ii)
    (princ (strcat "\r" (itoa (- (sslength ss2) cl)) "     "))
    (setq ma 400 mr 0 ms 0)
  )
)

;; DONT EVEN THINK ABOUT CHANGING THESE NUMBERS
(defun Load_Master_Data()
(setq MASTER (list
 '(0.00000000 0.00000000 1.00000000 1.00000000) '(0.57293870 99.00504987 0.00999950 100.00499988) '(1.14576284 49.01019894 0.01999600 50.00999900)
 '(1.71835800 33.01514653 0.00999550 100.04498988) '(2.29061004 24.02079105 0.03996804 25.01999201) '(2.86240523 19.02623206 0.04993762 20.02498439)
 '(3.43363036 33.06054448 0.01996410 50.08991914) '(4.00417294 57.14017764 0.00997559 100.24470061) '(4.57392126 12.04152856 0.03987261 25.07987241)
 '(5.14276456 11.04535653 0.00995974 100.40418318) '(5.71059314 9.05483843 0.09950372 10.04987562) '(6.27729849 9.05537968 0.00994004 100.60318087)
 '(6.84277341 8.06215993 0.03971507 25.17935662) '(7.40691213 23.19482489 0.00991656 100.84145973) '(7.96961039 7.07104007 0.01980683 50.48762224)
 '(8.53076561 13.15285349 0.04944682 20.22374842) '(9.09027692 6.08263429 0.03949763 25.31797780) '(9.64804532 47.67598874 0.00985856 101.43470806)
 '(10.20397372 11.18032256 0.01968367 50.80354318) '(10.75796709 21.37755607 0.00982424 101.78899744) '(11.30993247 4.11843884 0.19611614 5.09901951)
 '(11.85977912 19.41648537 0.00978653 102.18121158) '(12.40741853 9.21952377 0.01953289 51.19570295) '(12.95276451 13.34166050 0.00974555 102.61091560)
 '(13.49573328 4.12292216 0.03889549 25.70992026) '(14.03624347 3.15296313 0.24253563 4.12310563) '(14.57421620 23.76972077 0.01935645 51.66236541)
 '(15.10957512 38.32753458 0.00965429 103.58088627) '(15.64224646 7.28000799 0.03851856 25.96150997) '(16.17215902 32.28002335 0.00960429 104.12012294)
 '(16.69924423 3.16082674 0.09578263 10.44030651) '(17.22343619 30.36445140 0.00955157 104.69479453) '(17.74467163 3.16204817 0.03809697 26.24880950)
 '(18.26288994 3.16226340 0.00949629 105.30432090) '(18.77803322 49.64876274 0.01893545 52.81098370) '(19.29004622 18.02769461 0.04719292 21.18962011)
 '(19.79887635 11.70463940 0.03763550 26.57066051) '(20.30447371 28.79235857 0.00937862 106.62551290) '(20.80679101 22.47219728 0.01869567 53.48831648)
 '(21.30578362 44.01136118 0.00931655 107.33592129) '(21.80140949 2.22834406 0.18569534 5.38516481) '(22.29362916 42.15447680 0.00925252 108.07867505)
 '(22.78240573 20.61551988 0.01843964 54.23098745) '(23.26770481 101.23734447 0.00918669 108.85311204) '(23.74949449 9.84878975 0.03661260 27.31300056)
 '(24.22774532 12.08295994 0.04559608 21.93171220) '(24.70243023 14.31780953 0.01816981 55.03635162) '(25.17352452 18.78829205 0.00905024 110.49434375)
 '(25.64100582 2.23577718 0.03606092 27.73084925) '(26.10485401 56.79788657 0.00897990 111.35977730) '(26.56505118 1.34164079 0.44721360 2.23606798)
 '(27.02158159 55.00908944 0.00890835 112.25417587) '(27.47443163 25.94221927 0.03548867 28.17800560) '(27.92358972 93.94147072 0.00883573 113.17685276)
 '(28.36904629 42.05947801 0.01759811 56.82429058) '(28.81079374 10.29553693 0.04381080 22.82542442) '(29.24882634 18.35752658 0.03490024 28.65309756)
 '(29.68314018 8.06225307 0.00868777 115.10430053) '(30.11373315 35.84689248 0.01730062 57.80138407) '(30.54060485 70.83078374 0.00861269 116.10770862)
 '(30.96375653 3.60147029 0.17149859 5.83095190) '(31.38319106 69.11584426 0.00853704 117.13667231) '(31.79891282 34.13209210 0.01699805 58.83026432)
 '(32.21092772 86.28441301 0.00846092 118.19052415) '(32.61924307 16.64328288 0.03369086 29.68164416) '(33.02386756 3.60530755 0.04192218 23.85372088)
 '(33.42481118 3.60551264 0.01669219 59.90826320) '(33.82208522 116.76472040 0.00830770 120.37026211) '(34.21570213 26.62703337 0.03307706 30.23243292)
 '(34.60567555 86.26702691 0.00823080 121.49485586) '(34.99202020 8.60193517 0.08192319 12.20655561) '(35.37475184 84.62859997 0.00815383 122.64175472)
 '(35.75388725 22.20357958 0.03246137 30.80584360) '(36.12944414 78.00640957 0.00807687 123.81033883) '(36.50144112 33.60059139 0.01607684 62.20128616)
 '(36.86989765 1.40000000 0.20000000 5.00000000) '(37.23483398 26.40073836 0.03184649 31.40063694) '(37.59627115 109.80892467 0.00792329 126.21014222)
 '(37.95423088 52.00961210 0.01577005 63.41135545) '(38.30873557 103.23274644 0.00784682 127.44018205) '(38.65980825 1.40556386 0.15617376 6.40312424)
 '(39.00747255 101.67103786 0.00777064 128.68954892) '(39.35175263 50.44799065 0.01546536 64.66065264) '(39.69267315 68.88395997 0.00769481 129.95768542)
 '(40.03025927 24.83946581 0.03062819 32.64965544) '(40.36453657 9.21946574 0.03809697 26.24880949) '(40.69553104 56.72741639 0.01516370 65.94694838)
 '(41.02326902 102.06860410 0.00754443 132.54810447) '(41.34777722 22.67154821 0.03002854 33.30165161) '(41.66908262 121.82774702 0.00746997 133.86933928)
 '(41.98721250 1.41225888 0.07432941 13.45362404) '(42.30219437 120.34118142 0.00739605 135.20724832) '(42.61405597 17.69178152 0.02943724 33.97057550)
 '(42.92282523 58.72818698 0.00732272 136.56134153) '(43.22853026 23.34523051 0.01457255 68.62215386) '(43.53119929 1.41374890 0.03624997 27.58622845)
 '(43.83086067 1.41391915 0.02885549 34.65544691) '(44.12754288 93.34880796 0.00717792 139.31618714) '(44.42127443 1.41414142 0.01428426 70.00714249)
 '(44.71208393 1.41419571 0.00710651 140.71602609) '(45.00000000 0.70710678 0.70710678 1.41421356) '(45.28791607 139.30183039 0.00710651 140.71602609)
 '(45.57872557 68.59300107 0.01428426 70.00714249) '(45.87245712 45.96737918 0.00717792 139.31618714) '(46.16913933 33.24152775 0.02885549 34.65544691)
 '(46.46880071 26.17247955 0.03624997 27.58622845) '(46.77146974 45.27692335 0.01457255 68.62215386) '(47.07717477 77.83315454 0.00732272 136.56134153)
 '(47.38594403 16.27879398 0.02943724 33.97057550) '(47.69780563 14.86606691 0.00739605 135.20724832) '(48.01278750 12.04136517 0.07432941 13.45362404)
 '(48.33091738 12.04159226 0.00746997 133.86933928) '(48.65222278 10.63010340 0.03002854 33.30165161) '(48.97673098 30.47950037 0.00754443 132.54810447)
 '(49.30446896 9.21953199 0.01516370 65.94694838) '(49.63546343 17.02934375 0.03809697 26.24880949) '(49.96974073 7.81018962 0.03062819 32.64965544)
 '(50.30732685 61.07372545 0.00769481 129.95768542) '(50.64824737 14.21266199 0.01546536 64.66065264) '(50.99252745 27.01851105 0.00777064 128.68954892)
 '(51.34019175 4.99756038 0.15617376 6.40312424) '(51.69126443 24.20743560 0.00784682 127.44018205) '(52.04576912 11.40174335 0.01577005 63.41135545)
 '(52.40372885 16.40121755 0.00792329 126.21014222) '(52.76516602 4.99989858 0.03184649 31.40063694) '(53.13010235 3.60000000 0.20000000 5.00000000)
 '(53.49855888 28.60069477 0.01607684 62.20128616) '(53.87055586 45.80392925 0.00807687 123.81033883) '(54.24611275 8.60226402 0.03246137 30.80584360)
 '(54.62524816 38.01315474 0.00815383 122.64175472) '(55.00797980 3.60462045 0.08192319 12.20655561) '(55.39432445 35.22782895 0.00823080 121.49485586)
 '(55.78429787 3.60539955 0.03307706 30.23243292) '(56.17791478 3.60554170 0.00830770 120.37026211) '(56.57518882 56.30275057 0.01669219 59.90826320)
 '(56.97613244 20.24841333 0.04192218 23.85372088) '(57.38075693 13.03836128 0.03369086 29.68164416) '(57.78907228 31.90611115 0.00846092 118.19052415)
 '(58.20108718 24.69817222 0.01699805 58.83026432) '(58.61680894 48.02082806 0.00853704 117.13667231) '(59.03624347 2.22948161 0.17149859 5.83095190)
 '(59.45939515 45.27692487 0.00861269 116.10770862) '(59.88626685 21.95449158 0.01730062 57.80138407) '(60.31685982 107.04204746 0.00868777 115.10430053)
 '(60.75117366 10.29557099 0.03490024 28.65309756) '(61.18920626 12.52988749 0.04381080 22.82542442) '(61.63095371 14.76481257 0.01759811 56.82429058)
 '(62.07641028 19.23538203 0.00883573 113.17685276) '(62.52556837 2.23578634 0.03548867 28.17800560) '(62.97841841 57.24508643 0.00890835 112.25417587)
 '(63.43494882 0.89442719 0.44721360 2.23606798) '(63.89514599 54.56189072 0.00897990 111.35977730) '(64.35899418 25.49507207 0.03606092 27.73084925)
 '(64.82647548 91.70605170 0.00905024 110.49434375) '(65.29756977 40.71854209 0.01816981 55.03635162) '(65.77225468 9.84875226 0.04559608 21.93171220)
 '(66.25050551 17.46421082 0.03661260 27.31300056) '(66.73229519 7.61576757 0.00918669 108.85311204) '(67.21759427 33.61546757 0.01843964 54.23098745)
 '(67.70637084 65.92419825 0.00925252 108.07867505) '(68.19859051 3.15682075 0.18569534 5.38516481) '(68.69421638 63.32456011 0.00931655 107.33592129)
 '(69.19320899 31.01611920 0.01869567 53.48831648) '(69.69552629 77.83315432 0.00937862 106.62551290) '(70.20112365 14.86602111 0.03763550 26.57066051)
 '(70.70995378 3.16192549 0.04719292 21.18962011) '(71.22196678 3.16222097 0.01893545 52.81098370) '(71.73711006 102.14205750 0.00949629 105.30432090)
 '(72.25532837 23.08676133 0.03809697 26.24880950) '(72.77656381 74.33034312 0.00955157 104.69479453) '(73.30075577 7.27947977 0.09578263 10.44030651)
 '(73.82784098 71.84009958 0.00960429 104.12012294) '(74.35775354 18.68150198 0.03851856 25.96150997) '(74.89042488 65.25335169 0.00965429 103.58088627)
 '(75.42578380 27.89264465 0.01935645 51.66236541) '(75.96375653 0.97014250 0.24253563 4.12310563) '(76.50426672 21.58699810 0.03889549 25.70992026)
 '(77.04723549 89.26925509 0.00974555 102.61091560) '(77.59258147 41.97617918 0.01953289 51.19570295) '(78.14022088 82.76472621 0.00978653 102.18121158)
 '(78.69006753 0.98058068 0.19611614 5.09901951) '(79.24203291 80.41144137 0.00982424 101.78899744) '(79.79602628 39.62322062 0.01968367 50.80354318)
 '(80.35195468 53.75871932 0.00985856 101.43470806) '(80.90972308 19.23534351 0.03949763 25.31797780) '(81.46923439 7.07089492 0.04944682 20.22374842)
 '(82.03038961 43.41658217 0.01980683 50.48762224) '(82.59308787 77.64663484 0.00991656 100.84145973) '(83.15722659 17.11719670 0.03971507 25.17935662)
 '(83.72270151 91.54780118 0.00994004 100.60318087) '(84.28940686 0.99503719 0.09950372 10.04987562) '(84.85723544 89.35882665 0.00995974 100.40418318)
 '(85.42607874 13.03834384 0.03987261 25.07987241) '(85.99582706 43.10452297 0.00997559 100.24470061) '(86.56636964 17.02937466 0.01996410 50.08991914)
 '(87.13759477 0.99875234 0.04993762 20.02498439) '(87.70938996 0.99920096 0.03996804 25.01999201) '(88.28164200 67.02984335 0.00999550 100.04498988)
 '(88.85423716 0.99980006 0.01999600 50.00999900) '(89.42706130 0.99995000 0.00999950 100.00499988) '(90.00000000 0.00000000 1.00000000 1.00000000)
 '(90.57293870 99.00504987 0.00999950 100.00499988) '(91.14576284 49.01019894 0.01999600 50.00999900) '(91.71835800 33.01514653 0.00999550 100.04498988)
 '(92.29061004 24.02079105 0.03996804 25.01999201) '(92.86240523 19.02623206 0.04993762 20.02498439) '(93.43363036 33.06054448 0.01996410 50.08991914)
 '(94.00417294 57.14017764 0.00997559 100.24470061) '(94.57392126 12.04152856 0.03987261 25.07987241) '(95.14276456 11.04535653 0.00995974 100.40418318)
 '(95.14276456 11.04535653 0.00995974 100.40418318) '(95.71059314 9.05483843 0.09950372 10.04987562) '(96.27729849 9.05537968 0.00994004 100.60318087)
 '(96.84277341 8.06215993 0.03971507 25.17935662) '(97.40691213 23.19482489 0.00991656 100.84145973) '(98.53076561 13.15285349 0.04944682 20.22374842)
 '(99.09027692 6.08263429 0.03949763 25.31797780) '(99.64804532 47.67598874 0.00985856 101.43470806) '(100.20397372 11.18032256 0.01968367 50.80354318)
 '(100.75796709 21.37755607 0.00982424 101.78899744) '(101.30993247 4.11843884 0.19611614 5.09901951) '(101.85977912 19.41648537 0.00978653 102.18121158)
 '(102.40741853 9.21952377 0.01953289 51.19570295) '(102.95276451 13.34166050 0.00974555 102.61091560) '(103.49573328 4.12292216 0.03889549 25.70992026)
 '(104.03624347 3.15296313 0.24253563 4.12310563) '(104.57421620 23.76972077 0.01935645 51.66236541) '(105.10957512 38.32753458 0.00965429 103.58088627)
 '(105.64224646 7.28000799 0.03851856 25.96150997) '(106.17215902 32.28002335 0.00960429 104.12012294) '(106.69924423 3.16082674 0.09578263 10.44030651)
 '(107.22343619 30.36445140 0.00955157 104.69479453) '(107.74467163 3.16204817 0.03809697 26.24880950) '(108.26288994 3.16226340 0.00949629 105.30432090)
 '(108.77803322 49.64876274 0.01893545 52.81098370) '(109.29004622 18.02769461 0.04719292 21.18962011) '(109.79887635 11.70463940 0.03763550 26.57066051)
 '(110.30447371 28.79235857 0.00937862 106.62551290) '(110.80679101 22.47219728 0.01869567 53.48831648) '(111.30578362 44.01136118 0.00931655 107.33592129)
 '(111.80140949 2.22834406 0.18569534 5.38516481) '(112.29362916 42.15447680 0.00925252 108.07867505) '(112.78240573 20.61551988 0.01843964 54.23098745)
 '(113.26770481 101.23734447 0.00918669 108.85311204) '(113.74949449 9.84878975 0.03661260 27.31300056) '(114.22774532 12.08295994 0.04559608 21.93171220)
 '(114.70243023 14.31780953 0.01816981 55.03635162) '(115.17352452 18.78829205 0.00905024 110.49434375) '(115.64100582 2.23577718 0.03606092 27.73084925)
 '(116.10485401 56.79788657 0.00897990 111.35977730) '(116.56505118 1.34164079 0.44721360 2.23606798) '(117.02158159 55.00908944 0.00890835 112.25417587)
 '(117.47443163 25.94221927 0.03548867 28.17800560) '(117.92358972 93.94147072 0.00883573 113.17685276) '(118.36904629 42.05947801 0.01759811 56.82429058)
 '(118.81079374 10.29553693 0.04381080 22.82542442) '(119.24882634 18.35752658 0.03490024 28.65309756) '(119.68314018 8.06225307 0.00868777 115.10430053)
 '(120.11373315 35.84689248 0.01730062 57.80138407) '(120.54060485 70.83078374 0.00861269 116.10770862) '(120.96375653 3.60147029 0.17149859 5.83095190)
 '(121.38319106 69.11584426 0.00853704 117.13667231) '(121.79891282 34.13209210 0.01699805 58.83026432) '(122.21092772 86.28441301 0.00846092 118.19052415)
 '(122.61924307 16.64328288 0.03369086 29.68164416) '(123.02386756 3.60530755 0.04192218 23.85372088) '(123.42481118 3.60551264 0.01669219 59.90826320)
 '(123.82208522 116.76472040 0.00830770 120.37026211) '(124.21570213 26.62703337 0.03307706 30.23243292) '(124.60567555 86.26702691 0.00823080 121.49485586)
 '(124.99202020 8.60193517 0.08192319 12.20655561) '(125.37475184 84.62859997 0.00815383 122.64175472) '(125.75388725 22.20357958 0.03246137 30.80584360)
 '(126.12944414 78.00640957 0.00807687 123.81033883) '(126.50144112 33.60059139 0.01607684 62.20128616) '(126.86989765 1.40000000 0.20000000 5.00000000)
 '(127.23483398 26.40073836 0.03184649 31.40063694) '(127.59627115 109.80892467 0.00792329 126.21014222) '(127.95423088 52.00961210 0.01577005 63.41135545)
 '(128.30873557 103.23274644 0.00784682 127.44018205) '(128.65980825 1.40556386 0.15617376 6.40312424) '(129.00747255 101.67103786 0.00777064 128.68954892)
 '(129.35175263 50.44799065 0.01546536 64.66065264) '(129.69267315 68.88395997 0.00769481 129.95768542) '(130.03025927 24.83946581 0.03062819 32.64965544)
 '(130.36453657 9.21946574 0.03809697 26.24880949) '(130.69553104 56.72741639 0.01516370 65.94694838) '(131.02326902 102.06860410 0.00754443 132.54810447)
 '(131.34777722 22.67154821 0.03002854 33.30165161) '(131.66908262 121.82774702 0.00746997 133.86933928) '(131.98721250 1.41225888 0.07432941 13.45362404)
 '(132.30219437 120.34118142 0.00739605 135.20724832) '(132.61405597 17.69178152 0.02943724 33.97057550) '(132.92282523 58.72818698 0.00732272 136.56134153)
 '(133.22853026 23.34523051 0.01457255 68.62215386) '(133.53119929 1.41374890 0.03624997 27.58622845) '(133.83086067 1.41391915 0.02885549 34.65544691)
 '(134.12754288 93.34880796 0.00717792 139.31618714) '(134.42127443 1.41414142 0.01428426 70.00714249) '(134.71208393 1.41419571 0.00710651 140.71602609)
 '(135.00000000 0.70710678 0.70710678 1.41421356) '(135.28791607 139.30183039 0.00710651 140.71602609) '(135.57872557 68.59300107 0.01428426 70.00714249)
 '(135.87245712 45.96737918 0.00717792 139.31618714) '(136.16913933 33.24152775 0.02885549 34.65544691) '(136.46880071 26.17247955 0.03624997 27.58622845)
 '(136.77146974 45.27692335 0.01457255 68.62215386) '(137.07717477 77.83315454 0.00732272 136.56134153) '(137.38594403 16.27879398 0.02943724 33.97057550)
 '(137.69780563 14.86606691 0.00739605 135.20724832) '(138.01278750 12.04136517 0.07432941 13.45362404) '(138.33091738 12.04159226 0.00746997 133.86933928)
 '(138.65222278 10.63010340 0.03002854 33.30165161) '(138.97673098 30.47950037 0.00754443 132.54810447) '(139.30446896 9.21953199 0.01516370 65.94694838)
 '(139.63546343 17.02934375 0.03809697 26.24880949) '(139.96974073 7.81018962 0.03062819 32.64965544) '(140.30732685 61.07372545 0.00769481 129.95768542)
 '(140.64824737 14.21266199 0.01546536 64.66065264) '(140.99252745 27.01851105 0.00777064 128.68954892) '(141.34019175 4.99756038 0.15617376 6.40312424)
 '(141.69126443 24.20743560 0.00784682 127.44018205) '(142.04576912 11.40174335 0.01577005 63.41135545) '(142.40372885 16.40121755 0.00792329 126.21014222)
 '(142.76516602 4.99989858 0.03184649 31.40063694) '(143.13010235 3.60000000 0.20000000 5.00000000) '(143.49855888 28.60069477 0.01607684 62.20128616)
 '(143.87055586 45.80392925 0.00807687 123.81033883) '(144.24611275 8.60226402 0.03246137 30.80584360) '(144.62524816 38.01315474 0.00815383 122.64175472)
 '(145.00797980 3.60462045 0.08192319 12.20655561) '(145.39432445 35.22782895 0.00823080 121.49485586) '(145.78429787 3.60539955 0.03307706 30.23243292)
 '(146.17791478 3.60554170 0.00830770 120.37026211) '(146.57518882 56.30275057 0.01669219 59.90826320) '(146.97613244 20.24841333 0.04192218 23.85372088)
 '(147.38075693 13.03836128 0.03369086 29.68164416) '(147.78907228 31.90611115 0.00846092 118.19052415) '(148.20108718 24.69817222 0.01699805 58.83026432)
 '(148.61680894 48.02082806 0.00853704 117.13667231) '(149.03624347 2.22948161 0.17149859 5.83095190) '(149.45939515 45.27692487 0.00861269 116.10770862)
 '(149.88626685 21.95449158 0.01730062 57.80138407) '(150.31685982 107.04204746 0.00868777 115.10430053) '(150.75117366 10.29557099 0.03490024 28.65309756)
 '(151.18920626 12.52988749 0.04381080 22.82542442) '(151.63095371 14.76481257 0.01759811 56.82429058) '(152.07641028 19.23538203 0.00883573 113.17685276)
 '(152.52556837 2.23578634 0.03548867 28.17800560) '(152.97841841 57.24508643 0.00890835 112.25417587) '(153.43494882 0.89442719 0.44721360 2.23606798)
 '(153.89514599 54.56189072 0.00897990 111.35977730) '(154.35899418 25.49507207 0.03606092 27.73084925) '(154.82647548 91.70605170 0.00905024 110.49434375)
 '(155.29756977 40.71854209 0.01816981 55.03635162) '(155.77225468 9.84875226 0.04559608 21.93171220) '(156.25050551 17.46421082 0.03661260 27.31300056)
 '(156.73229519 7.61576757 0.00918669 108.85311204) '(157.21759427 33.61546757 0.01843964 54.23098745) '(157.70637084 65.92419825 0.00925252 108.07867505)
 '(158.19859051 3.15682075 0.18569534 5.38516481) '(158.69421638 63.32456011 0.00931655 107.33592129) '(159.19320899 31.01611920 0.01869567 53.48831648)
 '(159.69552629 77.83315432 0.00937862 106.62551290) '(160.20112365 14.86602111 0.03763550 26.57066051) '(160.70995378 3.16192549 0.04719292 21.18962011)
 '(161.22196678 3.16222097 0.01893545 52.81098370) '(161.73711006 102.14205750 0.00949629 105.30432090) '(162.25532837 23.08676133 0.03809697 26.24880950)
 '(162.77656381 74.33034312 0.00955157 104.69479453) '(163.30075577 7.27947977 0.09578263 10.44030651) '(163.82784098 71.84009958 0.00960429 104.12012294)
 '(164.35775354 18.68150198 0.03851856 25.96150997) '(164.89042488 65.25335169 0.00965429 103.58088627) '(165.42578380 27.89264465 0.01935645 51.66236541)
 '(165.96375653 0.97014250 0.24253563 4.12310563) '(166.50426672 21.58699810 0.03889549 25.70992026) '(167.04723549 89.26925509 0.00974555 102.61091560)
 '(167.59258147 41.97617918 0.01953289 51.19570295) '(168.14022088 82.76472621 0.00978653 102.18121158) '(168.69006753 0.98058068 0.19611614 5.09901951)
 '(169.24203291 80.41144137 0.00982424 101.78899744) '(169.79602628 39.62322062 0.01968367 50.80354318) '(170.35195468 53.75871932 0.00985856 101.43470806)
 '(170.90972308 19.23534351 0.03949763 25.31797780) '(171.46923439 7.07089492 0.04944682 20.22374842) '(172.03038961 43.41658217 0.01980683 50.48762224)
 '(172.59308787 77.64663484 0.00991656 100.84145973) '(173.15722659 17.11719670 0.03971507 25.17935662) '(173.72270151 91.54780118 0.00994004 100.60318087)
 '(174.28940686 0.99503719 0.09950372 10.04987562) '(174.85723544 89.35882665 0.00995974 100.40418318) '(175.42607874 13.03834384 0.03987261 25.07987241)
 '(175.99582706 43.10452297 0.00997559 100.24470061) '(176.56636964 17.02937466 0.01996410 50.08991914) '(177.13759477 0.99875234 0.04993762 20.02498439)
 '(177.70938996 0.99920096 0.03996804 25.01999201) '(178.28164200 67.02984335 0.00999550 100.04498988) '(178.85423716 0.99980006 0.01999600 50.00999900)
 '(179.42706130 0.99995000 0.00999950 100.00499988) '(180.00000000 0.00000000 1.00000000 1.00000000) '(180.57293870 99.00504987 0.00999950 100.00499988)
 '(181.14576284 49.01019894 0.01999600 50.00999900) '(181.71835800 33.01514653 0.00999550 100.04498988) '(182.29061004 24.02079105 0.03996804 25.01999201)
 '(182.86240523 19.02623206 0.04993762 20.02498439) '(183.43363036 33.06054448 0.01996410 50.08991914) '(184.00417294 57.14017764 0.00997559 100.24470061)
 '(184.57392126 12.04152856 0.03987261 25.07987241) '(185.14276456 11.04535653 0.00995974 100.40418318) '(185.14276456 11.04535653 0.00995974 100.40418318)
 '(185.71059314 9.05483843 0.09950372 10.04987562) '(186.27729849 9.05537968 0.00994004 100.60318087) '(186.84277341 8.06215993 0.03971507 25.17935662)
 '(187.40691213 23.19482489 0.00991656 100.84145973) '(188.53076561 13.15285349 0.04944682 20.22374842) '(189.09027692 6.08263429 0.03949763 25.31797780)
 '(189.64804532 47.67598874 0.00985856 101.43470806) '(190.20397372 11.18032256 0.01968367 50.80354318) '(190.75796709 21.37755607 0.00982424 101.78899744)
 '(191.30993247 4.11843884 0.19611614 5.09901951) '(191.85977912 19.41648537 0.00978653 102.18121158) '(192.40741853 9.21952377 0.01953289 51.19570295)
 '(192.95276451 13.34166050 0.00974555 102.61091560) '(193.49573328 4.12292216 0.03889549 25.70992026) '(194.03624347 3.15296313 0.24253563 4.12310563)
 '(194.57421620 23.76972077 0.01935645 51.66236541) '(195.10957512 38.32753458 0.00965429 103.58088627) '(195.64224646 7.28000799 0.03851856 25.96150997)
 '(196.17215902 32.28002335 0.00960429 104.12012294) '(196.69924423 3.16082674 0.09578263 10.44030651) '(197.22343619 30.36445140 0.00955157 104.69479453)
 '(197.74467163 3.16204817 0.03809697 26.24880950) '(198.26288994 3.16226340 0.00949629 105.30432090) '(198.77803322 49.64876274 0.01893545 52.81098370)
 '(199.29004622 18.02769461 0.04719292 21.18962011) '(199.79887635 11.70463940 0.03763550 26.57066051) '(200.30447371 28.79235857 0.00937862 106.62551290)
 '(200.80679101 22.47219728 0.01869567 53.48831648) '(201.30578362 44.01136118 0.00931655 107.33592129) '(201.80140949 2.22834406 0.18569534 5.38516481)
 '(202.29362916 42.15447680 0.00925252 108.07867505) '(202.78240573 20.61551988 0.01843964 54.23098745) '(203.26770481 101.23734447 0.00918669 108.85311204)
 '(203.74949449 9.84878975 0.03661260 27.31300056) '(204.22774532 12.08295994 0.04559608 21.93171220) '(204.70243023 14.31780953 0.01816981 55.03635162)
 '(205.17352452 18.78829205 0.00905024 110.49434375) '(205.64100582 2.23577718 0.03606092 27.73084925) '(206.10485401 56.79788657 0.00897990 111.35977730)
 '(206.56505118 1.34164079 0.44721360 2.23606798) '(207.02158159 55.00908944 0.00890835 112.25417587) '(207.47443163 25.94221927 0.03548867 28.17800560)
 '(207.92358972 93.94147072 0.00883573 113.17685276) '(208.36904629 42.05947801 0.01759811 56.82429058) '(208.81079374 10.29553693 0.04381080 22.82542442)
 '(209.24882634 18.35752658 0.03490024 28.65309756) '(209.68314018 8.06225307 0.00868777 115.10430053) '(210.11373315 35.84689248 0.01730062 57.80138407)
 '(210.54060485 70.83078374 0.00861269 116.10770862) '(210.96375653 3.60147029 0.17149859 5.83095190) '(211.38319106 69.11584426 0.00853704 117.13667231)
 '(211.79891282 34.13209210 0.01699805 58.83026432) '(212.21092772 86.28441301 0.00846092 118.19052415) '(212.61924307 16.64328288 0.03369086 29.68164416)
 '(213.02386756 3.60530755 0.04192218 23.85372088) '(213.42481118 3.60551264 0.01669219 59.90826320) '(213.82208522 116.76472040 0.00830770 120.37026211)
 '(214.21570213 26.62703337 0.03307706 30.23243292) '(214.60567555 86.26702691 0.00823080 121.49485586) '(214.99202020 8.60193517 0.08192319 12.20655561)
 '(215.37475184 84.62859997 0.00815383 122.64175472) '(215.75388725 22.20357958 0.03246137 30.80584360) '(216.12944414 78.00640957 0.00807687 123.81033883)
 '(216.50144112 33.60059139 0.01607684 62.20128616) '(216.86989765 1.40000000 0.20000000 5.00000000) '(217.23483398 26.40073836 0.03184649 31.40063694)
 '(217.59627115 109.80892467 0.00792329 126.21014222) '(217.95423088 52.00961210 0.01577005 63.41135545) '(218.30873557 103.23274644 0.00784682 127.44018205)
 '(218.65980825 1.40556386 0.15617376 6.40312424) '(219.00747255 101.67103786 0.00777064 128.68954892) '(219.35175263 50.44799065 0.01546536 64.66065264)
 '(219.69267315 68.88395997 0.00769481 129.95768542) '(220.03025927 24.83946581 0.03062819 32.64965544) '(220.36453657 9.21946574 0.03809697 26.24880949)
 '(220.69553104 56.72741639 0.01516370 65.94694838) '(221.02326902 102.06860410 0.00754443 132.54810447) '(221.34777722 22.67154821 0.03002854 33.30165161)
 '(221.66908262 121.82774702 0.00746997 133.86933928) '(221.98721250 1.41225888 0.07432941 13.45362404) '(222.30219437 120.34118142 0.00739605 135.20724832)
 '(222.61405597 17.69178152 0.02943724 33.97057550) '(222.92282523 58.72818698 0.00732272 136.56134153) '(223.22853026 23.34523051 0.01457255 68.62215386)
 '(223.53119929 1.41374890 0.03624997 27.58622845) '(223.83086067 1.41391915 0.02885549 34.65544691) '(224.12754288 93.34880796 0.00717792 139.31618714)
 '(224.42127443 1.41414142 0.01428426 70.00714249) '(224.71208393 1.41419571 0.00710651 140.71602609) '(225.00000000 0.70710678 0.70710678 1.41421356)
 '(225.28791607 139.30183039 0.00710651 140.71602609) '(225.57872557 68.59300107 0.01428426 70.00714249) '(225.87245712 45.96737918 0.00717792 139.31618714)
 '(226.16913933 33.24152775 0.02885549 34.65544691) '(226.46880071 26.17247955 0.03624997 27.58622845) '(226.77146974 45.27692335 0.01457255 68.62215386)
 '(227.07717477 77.83315454 0.00732272 136.56134153) '(227.38594403 16.27879398 0.02943724 33.97057550) '(227.69780563 14.86606691 0.00739605 135.20724832)
 '(228.01278750 12.04136517 0.07432941 13.45362404) '(228.33091738 12.04159226 0.00746997 133.86933928) '(228.65222278 10.63010340 0.03002854 33.30165161)
 '(228.97673098 30.47950037 0.00754443 132.54810447) '(229.30446896 9.21953199 0.01516370 65.94694838) '(229.63546343 17.02934375 0.03809697 26.24880949)
 '(229.96974073 7.81018962 0.03062819 32.64965544) '(230.30732685 61.07372545 0.00769481 129.95768542) '(230.64824737 14.21266199 0.01546536 64.66065264)
 '(230.99252745 27.01851105 0.00777064 128.68954892) '(231.34019175 4.99756038 0.15617376 6.40312424) '(231.69126443 24.20743560 0.00784682 127.44018205)
 '(232.04576912 11.40174335 0.01577005 63.41135545) '(232.40372885 16.40121755 0.00792329 126.21014222) '(232.76516602 4.99989858 0.03184649 31.40063694)
 '(233.13010235 3.60000000 0.20000000 5.00000000) '(233.49855888 28.60069477 0.01607684 62.20128616) '(233.87055586 45.80392925 0.00807687 123.81033883)
 '(234.24611275 8.60226402 0.03246137 30.80584360) '(234.62524816 38.01315474 0.00815383 122.64175472) '(235.00797980 3.60462045 0.08192319 12.20655561)
 '(235.39432445 35.22782895 0.00823080 121.49485586) '(235.78429787 3.60539955 0.03307706 30.23243292) '(236.17791478 3.60554170 0.00830770 120.37026211)
 '(236.57518882 56.30275057 0.01669219 59.90826320) '(236.97613244 20.24841333 0.04192218 23.85372088) '(237.38075693 13.03836128 0.03369086 29.68164416)
 '(237.78907228 31.90611115 0.00846092 118.19052415) '(238.20108718 24.69817222 0.01699805 58.83026432) '(238.61680894 48.02082806 0.00853704 117.13667231)
 '(239.03624347 2.22948161 0.17149859 5.83095190) '(239.45939515 45.27692487 0.00861269 116.10770862) '(239.88626685 21.95449158 0.01730062 57.80138407)
 '(240.31685982 107.04204746 0.00868777 115.10430053) '(240.75117366 10.29557099 0.03490024 28.65309756) '(241.18920626 12.52988749 0.04381080 22.82542442)
 '(241.63095371 14.76481257 0.01759811 56.82429058) '(242.07641028 19.23538203 0.00883573 113.17685276) '(242.52556837 2.23578634 0.03548867 28.17800560)
 '(242.97841841 57.24508643 0.00890835 112.25417587) '(243.43494882 0.89442719 0.44721360 2.23606798) '(243.89514599 54.56189072 0.00897990 111.35977730)
 '(244.35899418 25.49507207 0.03606092 27.73084925) '(244.82647548 91.70605170 0.00905024 110.49434375) '(245.29756977 40.71854209 0.01816981 55.03635162)
 '(245.77225468 9.84875226 0.04559608 21.93171220) '(246.25050551 17.46421082 0.03661260 27.31300056) '(246.73229519 7.61576757 0.00918669 108.85311204)
 '(247.21759427 33.61546757 0.01843964 54.23098745) '(247.70637084 65.92419825 0.00925252 108.07867505) '(248.19859051 3.15682075 0.18569534 5.38516481)
 '(248.69421638 63.32456011 0.00931655 107.33592129) '(249.19320899 31.01611920 0.01869567 53.48831648) '(249.69552629 77.83315432 0.00937862 106.62551290)
 '(250.20112365 14.86602111 0.03763550 26.57066051) '(250.70995378 3.16192549 0.04719292 21.18962011) '(251.22196678 3.16222097 0.01893545 52.81098370)
 '(251.73711006 102.14205750 0.00949629 105.30432090) '(252.25532837 23.08676133 0.03809697 26.24880950) '(252.77656381 74.33034312 0.00955157 104.69479453)
 '(253.30075577 7.27947977 0.09578263 10.44030651) '(253.82784098 71.84009958 0.00960429 104.12012294) '(254.35775354 18.68150198 0.03851856 25.96150997)
 '(254.89042488 65.25335169 0.00965429 103.58088627) '(255.42578380 27.89264465 0.01935645 51.66236541) '(255.96375653 0.97014250 0.24253563 4.12310563)
 '(256.50426672 21.58699810 0.03889549 25.70992026) '(257.04723549 89.26925509 0.00974555 102.61091560) '(257.59258147 41.97617918 0.01953289 51.19570295)
 '(258.14022088 82.76472621 0.00978653 102.18121158) '(258.69006753 0.98058068 0.19611614 5.09901951) '(259.24203291 80.41144137 0.00982424 101.78899744)
 '(259.79602628 39.62322062 0.01968367 50.80354318) '(260.35195468 53.75871932 0.00985856 101.43470806) '(260.90972308 19.23534351 0.03949763 25.31797780)
 '(261.46923439 7.07089492 0.04944682 20.22374842) '(262.59308787 77.64663484 0.00991656 100.84145973) '(263.15722659 17.11719670 0.03971507 25.17935662)
 '(263.72270151 91.54780118 0.00994004 100.60318087) '(264.28940686 0.99503719 0.09950372 10.04987562) '(264.85723544 89.35882665 0.00995974 100.40418318)
 '(264.85723544 89.35882665 0.00995974 100.40418318) '(265.42607874 13.03834384 0.03987261 25.07987241) '(265.99582706 43.10452297 0.00997559 100.24470061)
 '(266.56636964 17.02937466 0.01996410 50.08991914) '(267.13759477 0.99875234 0.04993762 20.02498439) '(267.70938996 0.99920096 0.03996804 25.01999201)
 '(268.28164200 67.02984335 0.00999550 100.04498988) '(268.85423716 0.99980006 0.01999600 50.00999900) '(269.42706130 0.99995000 0.00999950 100.00499988)
 '(270.00000000 0.00000000 1.00000000 1.00000000) '(270.57293870 99.00504987 0.00999950 100.00499988) '(271.14576284 49.01019894 0.01999600 50.00999900)
 '(271.71835800 33.01514653 0.00999550 100.04498988) '(272.29061004 24.02079105 0.03996804 25.01999201) '(272.86240523 19.02623206 0.04993762 20.02498439)
 '(273.43363036 33.06054448 0.01996410 50.08991914) '(274.00417294 57.14017764 0.00997559 100.24470061) '(274.57392126 12.04152856 0.03987261 25.07987241)
 '(275.14276456 11.04535653 0.00995974 100.40418318) '(275.71059314 9.05483843 0.09950372 10.04987562) '(276.27729849 9.05537968 0.00994004 100.60318087)
 '(276.84277341 8.06215993 0.03971507 25.17935662) '(277.40691213 23.19482489 0.00991656 100.84145973) '(277.96961039 7.07104007 0.01980683 50.48762224)
 '(278.53076561 13.15285349 0.04944682 20.22374842) '(279.09027692 6.08263429 0.03949763 25.31797780) '(279.64804532 47.67598874 0.00985856 101.43470806)
 '(280.20397372 11.18032256 0.01968367 50.80354318) '(280.75796709 21.37755607 0.00982424 101.78899744) '(281.30993247 4.11843884 0.19611614 5.09901951)
 '(281.85977912 19.41648537 0.00978653 102.18121158) '(282.40741853 9.21952377 0.01953289 51.19570295) '(282.95276451 13.34166050 0.00974555 102.61091560)
 '(283.49573328 4.12292216 0.03889549 25.70992026) '(284.03624347 3.15296313 0.24253563 4.12310563) '(284.57421620 23.76972077 0.01935645 51.66236541)
 '(285.10957512 38.32753458 0.00965429 103.58088627) '(285.64224646 7.28000799 0.03851856 25.96150997) '(286.17215902 32.28002335 0.00960429 104.12012294)
 '(286.69924423 3.16082674 0.09578263 10.44030651) '(287.22343619 30.36445140 0.00955157 104.69479453) '(287.74467163 3.16204817 0.03809697 26.24880950)
 '(288.26288994 3.16226340 0.00949629 105.30432090) '(288.77803322 49.64876274 0.01893545 52.81098370) '(289.29004622 18.02769461 0.04719292 21.18962011)
 '(289.79887635 11.70463940 0.03763550 26.57066051) '(290.30447371 28.79235857 0.00937862 106.62551290) '(290.80679101 22.47219728 0.01869567 53.48831648)
 '(291.30578362 44.01136118 0.00931655 107.33592129) '(291.80140949 2.22834406 0.18569534 5.38516481) '(292.29362916 42.15447680 0.00925252 108.07867505)
 '(292.78240573 20.61551988 0.01843964 54.23098745) '(293.26770481 101.23734447 0.00918669 108.85311204) '(293.74949449 9.84878975 0.03661260 27.31300056)
 '(294.22774532 12.08295994 0.04559608 21.93171220) '(294.70243023 14.31780953 0.01816981 55.03635162) '(295.17352452 18.78829205 0.00905024 110.49434375)
 '(295.64100582 2.23577718 0.03606092 27.73084925) '(296.10485401 56.79788657 0.00897990 111.35977730) '(296.56505118 1.34164079 0.44721360 2.23606798)
 '(297.02158159 55.00908944 0.00890835 112.25417587) '(297.47443163 25.94221927 0.03548867 28.17800560) '(297.92358972 93.94147072 0.00883573 113.17685276)
 '(298.36904629 42.05947801 0.01759811 56.82429058) '(298.81079374 10.29553693 0.04381080 22.82542442) '(299.24882634 18.35752658 0.03490024 28.65309756)
 '(299.68314018 8.06225307 0.00868777 115.10430053) '(300.11373315 35.84689248 0.01730062 57.80138407) '(300.54060485 70.83078374 0.00861269 116.10770862)
 '(300.96375653 3.60147029 0.17149859 5.83095190) '(301.38319106 69.11584426 0.00853704 117.13667231) '(301.79891282 34.13209210 0.01699805 58.83026432)
 '(302.21092772 86.28441301 0.00846092 118.19052415) '(302.61924307 16.64328288 0.03369086 29.68164416) '(303.02386756 3.60530755 0.04192218 23.85372088)
 '(303.42481118 3.60551264 0.01669219 59.90826320) '(303.82208522 116.76472040 0.00830770 120.37026211) '(304.21570213 26.62703337 0.03307706 30.23243292)
 '(304.60567555 86.26702691 0.00823080 121.49485586) '(304.99202020 8.60193517 0.08192319 12.20655561) '(305.37475184 84.62859997 0.00815383 122.64175472)
 '(305.75388725 22.20357958 0.03246137 30.80584360) '(306.12944414 78.00640957 0.00807687 123.81033883) '(306.50144112 33.60059139 0.01607684 62.20128616)
 '(306.86989765 1.40000000 0.20000000 5.00000000) '(307.23483398 26.40073836 0.03184649 31.40063694) '(307.59627115 109.80892467 0.00792329 126.21014222)
 '(307.95423088 52.00961210 0.01577005 63.41135545) '(308.30873557 103.23274644 0.00784682 127.44018205) '(308.65980825 1.40556386 0.15617376 6.40312424)
 '(309.00747255 101.67103786 0.00777064 128.68954892) '(309.35175263 50.44799065 0.01546536 64.66065264) '(309.69267315 68.88395997 0.00769481 129.95768542)
 '(310.03025927 24.83946581 0.03062819 32.64965544) '(310.36453657 9.21946574 0.03809697 26.24880949) '(310.69553104 56.72741639 0.01516370 65.94694838)
 '(311.02326902 102.06860410 0.00754443 132.54810447) '(311.34777722 22.67154821 0.03002854 33.30165161) '(311.66908262 121.82774702 0.00746997 133.86933928)
 '(311.98721250 1.41225888 0.07432941 13.45362404) '(312.30219437 120.34118142 0.00739605 135.20724832) '(312.61405597 17.69178152 0.02943724 33.97057550)
 '(312.92282523 58.72818698 0.00732272 136.56134153) '(313.22853026 23.34523051 0.01457255 68.62215386) '(313.53119929 1.41374890 0.03624997 27.58622845)
 '(313.83086067 1.41391915 0.02885549 34.65544691) '(314.12754288 93.34880796 0.00717792 139.31618714) '(314.42127443 1.41414142 0.01428426 70.00714249)
 '(314.71208393 1.41419571 0.00710651 140.71602609) '(315.00000000 0.70710678 0.70710678 1.41421356) '(315.28791607 139.30183039 0.00710651 140.71602609)
 '(315.57872557 68.59300107 0.01428426 70.00714249) '(315.87245712 45.96737918 0.00717792 139.31618714) '(316.16913933 33.24152775 0.02885549 34.65544691)
 '(316.46880071 26.17247955 0.03624997 27.58622845) '(316.77146974 45.27692335 0.01457255 68.62215386) '(317.07717477 77.83315454 0.00732272 136.56134153)
 '(317.38594403 16.27879398 0.02943724 33.97057550) '(317.69780563 14.86606691 0.00739605 135.20724832) '(318.01278750 12.04136517 0.07432941 13.45362404)
 '(318.33091738 12.04159226 0.00746997 133.86933928) '(318.65222278 10.63010340 0.03002854 33.30165161) '(318.97673098 30.47950037 0.00754443 132.54810447)
 '(319.30446896 9.21953199 0.01516370 65.94694838) '(319.63546343 17.02934375 0.03809697 26.24880949) '(319.96974073 7.81018962 0.03062819 32.64965544)
 '(320.30732685 61.07372545 0.00769481 129.95768542) '(320.64824737 14.21266199 0.01546536 64.66065264) '(320.99252745 27.01851105 0.00777064 128.68954892)
 '(321.34019175 4.99756038 0.15617376 6.40312424) '(321.69126443 24.20743560 0.00784682 127.44018205) '(322.04576912 11.40174335 0.01577005 63.41135545)
 '(322.40372885 16.40121755 0.00792329 126.21014222) '(322.76516602 4.99989858 0.03184649 31.40063694) '(323.13010235 3.60000000 0.20000000 5.00000000)
 '(323.49855888 28.60069477 0.01607684 62.20128616) '(323.87055586 45.80392925 0.00807687 123.81033883) '(324.24611275 8.60226402 0.03246137 30.80584360)
 '(324.62524816 38.01315474 0.00815383 122.64175472) '(325.00797980 3.60462045 0.08192319 12.20655561) '(325.39432445 35.22782895 0.00823080 121.49485586)
 '(325.78429787 3.60539955 0.03307706 30.23243292) '(326.17791478 3.60554170 0.00830770 120.37026211) '(326.57518882 56.30275057 0.01669219 59.90826320)
 '(326.97613244 20.24841333 0.04192218 23.85372088) '(327.38075693 13.03836128 0.03369086 29.68164416) '(327.78907228 31.90611115 0.00846092 118.19052415)
 '(328.20108718 24.69817222 0.01699805 58.83026432) '(328.61680894 48.02082806 0.00853704 117.13667231) '(329.03624347 2.22948161 0.17149859 5.83095190)
 '(329.45939515 45.27692487 0.00861269 116.10770862) '(329.88626685 21.95449158 0.01730062 57.80138407) '(330.31685982 107.04204746 0.00868777 115.10430053)
 '(330.75117366 10.29557099 0.03490024 28.65309756) '(331.18920626 12.52988749 0.04381080 22.82542442) '(331.63095371 14.76481257 0.01759811 56.82429058)
 '(332.07641028 19.23538203 0.00883573 113.17685276) '(332.52556837 2.23578634 0.03548867 28.17800560) '(332.97841841 57.24508643 0.00890835 112.25417587)
 '(333.43494882 0.89442719 0.44721360 2.23606798) '(333.89514599 54.56189072 0.00897990 111.35977730) '(334.35899418 25.49507207 0.03606092 27.73084925)
 '(334.82647548 91.70605170 0.00905024 110.49434375) '(335.29756977 40.71854209 0.01816981 55.03635162) '(335.77225468 9.84875226 0.04559608 21.93171220)
 '(336.25050551 17.46421082 0.03661260 27.31300056) '(336.73229519 7.61576757 0.00918669 108.85311204) '(337.21759427 33.61546757 0.01843964 54.23098745)
 '(337.70637084 65.92419825 0.00925252 108.07867505) '(338.19859051 3.15682075 0.18569534 5.38516481) '(338.69421638 63.32456011 0.00931655 107.33592129)
 '(339.19320899 31.01611920 0.01869567 53.48831648) '(339.69552629 77.83315432 0.00937862 106.62551290) '(340.20112365 14.86602111 0.03763550 26.57066051)
 '(340.70995378 3.16192549 0.04719292 21.18962011) '(341.22196678 3.16222097 0.01893545 52.81098370) '(341.73711006 102.14205750 0.00949629 105.30432090)
 '(342.25532837 23.08676133 0.03809697 26.24880950) '(342.77656381 74.33034312 0.00955157 104.69479453) '(343.30075577 7.27947977 0.09578263 10.44030651)
 '(343.82784098 71.84009958 0.00960429 104.12012294) '(344.35775354 18.68150198 0.03851856 25.96150997) '(344.89042488 65.25335169 0.00965429 103.58088627)
 '(345.42578380 27.89264465 0.01935645 51.66236541) '(345.96375653 0.97014250 0.24253563 4.12310563) '(346.50426672 21.58699810 0.03889549 25.70992026)
 '(347.04723549 89.26925509 0.00974555 102.61091560) '(347.59258147 41.97617918 0.01953289 51.19570295) '(348.14022088 82.76472621 0.00978653 102.18121158)
 '(348.69006753 0.98058068 0.19611614 5.09901951) '(349.24203291 80.41144137 0.00982424 101.78899744) '(349.79602628 39.62322062 0.01968367 50.80354318)
 '(350.35195468 53.75871932 0.00985856 101.43470806) '(350.90972308 19.23534351 0.03949763 25.31797780) '(351.46923439 7.07089492 0.04944682 20.22374842)
 '(352.59308787 77.64663484 0.00991656 100.84145973) '(353.15722659 17.11719670 0.03971507 25.17935662) '(353.72270151 91.54780118 0.00994004 100.60318087)
 '(354.28940686 0.99503719 0.09950372 10.04987562) '(354.85723544 89.35882665 0.00995974 100.40418318) '(354.85723544 89.35882665 0.00995974 100.40418318)
 '(355.42607874 13.03834384 0.03987261 25.07987241) '(355.99582706 43.10452297 0.00997559 100.24470061) '(356.56636964 17.02937466 0.01996410 50.08991914)
 '(357.13759477 0.99875234 0.04993762 20.02498439) '(357.70938996 0.99920096 0.03996804 25.01999201) '(358.28164200 67.02984335 0.00999550 100.04498988)
 '(358.85423716 0.99980006 0.01999600 50.00999900) '(359.42706130 0.99995000 0.00999950 100.00499988) '(360.00000000 0.00000000 1.00000000 1.00000000)
)))
